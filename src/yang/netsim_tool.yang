module netsim_tool {

  namespace "http://nil.com/netsim_tool";
  prefix netsim_tool;

  import tailf-common {
    prefix tailf;
  }
  import tailf-ncs {
    prefix ncs;
  }

  description "A library of actions for adding netsim devices";

   // =========================================================================
   // REVISION
   // =========================================================================

   revision 2018-05-06 {
     description
     "contact: sspehar@nil.com
     ";
   }

   // =========================================================================
   // TYPEDEF
   // =========================================================================

   typedef ned-id {
	type union {
		type enumeration {
			enum "juniper-junos";
			enum "cisco-ios";
			enum "cisco-iosxr";
			enum "paloalto-panos_cli";
		}
		type string;
	}
   }
  
  
  
	  container netsim {
			container config {
				tailf:info "Netsim configuration";
				leaf netsim-dir {
					tailf:info "Absolute path to the netsim directory";
					type string;
					default "/netsim-lab";
				}

				leaf IPC_PORT {
					tailf:info "Default 5010";
					type uint32;
					default 5010;
				}

				leaf NETCONF_SSH_PORT {
					tailf:info "12022";
					type uint32;
					default 12022;
				}

				leaf NETCONF_TCP_PORT {
					tailf:info "13022";
					type uint32;
					default 13022;

				}

				leaf SNMP_PORT {
					tailf:info "11022";
					type uint32;
					default 11022;
				}

				leaf CLI_SSH_PORT {
					tailf:info "10022";
					type uint32;
					default 10022;
				}
							
			}

			tailf:action create-network {
				tailf:info "Create new Netsim network";
				tailf:actionpoint netsim-tool;
				input {
					leaf ned-id {
						tailf:info "NED ID";
						mandatory true;
						type ned-id;
					}
					leaf number {
						mandatory true;
						tailf:info "Number of devices";
						type uint8;
					}
					leaf prefix {
						mandatory true;
						tailf:info "Prefix for devices";
						type string;
					}
				}
				output {
					leaf result {
						type boolean;
					}
					
					leaf info {
						type string;
					}	
				}
			}
			tailf:action create-device {
				tailf:info "Create new Netsim network with one device";
				tailf:actionpoint netsim-tool;
				input {
					leaf ned-id {
						tailf:info "NED ID";
						mandatory true;
						type ned-id;	
					}
					leaf device-name {
						tailf:info "Device name";
						mandatory true;
						type string;
					}
				}
				output {
					leaf result {
						type boolean;
					}
					
					leaf info {
						type string;
					}	
				}
			}

			
			tailf:action delete-network {
				tailf:info "Delete currently configured Netsim network";
				tailf:actionpoint netsim-tool;
				output {
					leaf result {
						type boolean;
					}
					
					leaf info {
						type string;
					}
					
				}
			}
			
			tailf:action add-device {
				tailf:info "Add device(s) to network";
				tailf:actionpoint netsim-tool;
				input {
					leaf ned-id {
						tailf:info "NED ID";
						mandatory true;
						type ned-id;
					}
				
					leaf-list device-name {
						type string;
					}
				}
				output {
					leaf result {
						type boolean;
					}
				
					leaf info {
						type string;
					}
				}
			}
			
			tailf:action start {
				tailf:info "Start Netsim device(s)";
				tailf:actionpoint netsim-tool;
				input {
					leaf-list device-name {
						type leafref { path "/ncs:devices/ncs:device/ncs:name"; } 
					}
				}
				output {
					leaf result {
						type boolean;
					}
				
					leaf info {
						type string;
					}
				}
			}
			
			tailf:action stop {
				tailf:info "Stop Netsim device(s)";
				tailf:actionpoint netsim-tool;
				input {
					leaf-list device-name {
						type leafref { path "/ncs:devices/ncs:device/ncs:name"; } 
					}
				}
				output {
					leaf result {
						type boolean;
					}
				
					leaf info {
						type string;
					}
				}
			}

			tailf:action is-alive {
				tailf:info "Check device(s) aliveness";
				tailf:actionpoint netsim-tool;
				input {
					leaf-list device-name {
						type leafref { path "/ncs:devices/ncs:device/ncs:name"; } 
					}
				}
				output {
					leaf result {
						type boolean;
					}
				
					leaf info {
						type string;
					}
				}
			}

			tailf:action list {
				tailf:info "List netsim devices";
				tailf:actionpoint netsim-tool;
				output {
					leaf result {
						type boolean;
					}

					leaf info {
						type string;
					}
				}
			}

			tailf:action load {
				tailf:info "Load devices from the 'netsim-dir'";
				tailf:actionpoint netsim-tool;
				output {
					leaf result {
						type boolean;
					}

					leaf info {
						type string;
					}
				}
			}

			tailf:action update-network {
				tailf:info "Update netsim fxs when NSO is updated";
				tailf:actionpoint netsim-tool;
				input {
				    //TODO: automatically find current ncs-run
					leaf ncs-run {
						tailf:info "Absolute path to current running directory";
						type string;
						mandatory true;
					}
				}
				output {
					leaf result {
						type boolean;
					}
					
					leaf info {
						type string;
					}
					
				}
			}
		
	  }

}
